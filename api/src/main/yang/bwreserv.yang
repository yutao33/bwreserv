module bwreserv {
    yang-version 1;
    namespace "urn:opendaylight:params:xml:ns:yang:bwreserv";
    prefix "bwreserv";

    revision "2015-01-05" {
        description "Initial revision of bwreserv model";
    }

    typedef link-id-type {
        type string;
    }
    typedef node-id-type {
        type string;
    }

    container tx{
        leaf bw{
            type int64;
        }
    }

    container graph {
        list node {
            key "nodeid";
            leaf nodeid {
                type node-id-type;
            }
            leaf-list node-links {
                type link-id-type;
            }
        }
        list link {
            key "linkid";
            leaf linkid {
                type link-id-type;
            }
            leaf from {
                type node-id-type;
            }
            leaf to {
                type node-id-type;
            }
            leaf bw {
                type int64;
            }
        }
    }

    rpc eval-func {
        input {
            leaf parm {
                type int64;
            }
        }
        output {
            leaf result {
                type string;
            }
        }
    }
}
